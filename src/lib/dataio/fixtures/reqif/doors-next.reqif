# System Requirements
Export of module System Requirements

# Specification: System Requirements

## 1001: Flight performance (Heading)

### 1002: Hover endurance (System Requirement)
The drone shall hover for at least 20 minutes with a 1 kg payload.
Conditions:
- still air,
- 15 °C at sea level.
- Status: Approved
- Priority: High
- Verification Method: Test, Analysis
- Modified On: 2026-09-12T14:31:07.000Z

#### 1003: Battery reserve (System Requirement)
The drone shall land with at least 15 % of its battery charge left.
The reserve shall be shown to the pilot.
- Priority: Medium
- Verification Method: Inspection
- Derived From -> 1002

### _so_1004 (Information)
Endurance figures assume the standard 6S battery.

## 1005: Safety (Heading)

### 1006: Geofence (System Requirement)
The drone shall not leave the approved flight area.
- Status: To Be Determined
- Priority: High
- Satisfies -> 1002

### 1007: Geofence warning (System Requirement)
The drone shall warn the pilot when it is within 20 m of the boundary of the approved flight area.
- Priority: Medium
- Derived From -> 1006
