# DRN Software Requirements

# Specification: Software Requirements Specification

## DRN-1: Flight control software (Heading)

### DRN-12: Attitude loop rate (Software Requirement)
The attitude controller shall run at 400 Hz or faster, and:
1. read the IMU every cycle;
2. log a missed deadline.
- Status: Approved
- Severity: Must Have
- Safety Relevant: true
- Initial Estimate: 3.5
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
### DRN-13: Motor output limits (Software Requirement)
The mixer shall keep each motor command within the limits below.
| Limit | Value |
| --- | --- |
| Minimum | 5 % |
| Maximum | 95 % |
- Status: Draft
- Severity: Should Have
- Safety Relevant: false
- relates to -> DRN-12

### DRN-14: Motor saturation alarm (Software Requirement)
When a motor command has been at its maximum for more than 2 s, the software shall raise a saturation alarm.
- Status: Reviewed
- Severity: Nice to Have
- refines -> DRN-13
