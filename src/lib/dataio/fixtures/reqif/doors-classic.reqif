# /Drone/Interfaces/Ground Station ICD

# Specification: Ground Station ICD

## _D9_O1: Telemetry link

### _D9_O2
The ground station shall receive telemetry at 10 Hz.

#### _D9_O3
Each telemetry frame shall carry:
- position,
- battery state, with
- voltage
- charge left
