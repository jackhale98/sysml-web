# Delivery Drone - Stakeholder Needs

# Specification: Stakeholder Needs

## jama-item-88001: Operations (Folder)

### DD-STK-7: Clear landing zone (Stakeholder Need)
The operator needs the drone to land only where nobody stands.
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- Global ID: GID-104882
- Status: Accepted
- Priority: High
- Rationale: Required by the operating approval.

### DD-STK-8: Landing zone check (Stakeholder Need)
The drone shall check the landing zone with its downward camera before it descends below 10 m.
- Global ID: GID-104883
- Status: Draft
- Derived from -> DD-STK-7
